FME workspace dgnv8_to_gpkg.fmw

Parameters:
- DestDataset_OGCGEOPACKAGE =
- DestDataset_SHAPEFILE =
- FEATURE_TYPES =
- SourceDataset_DGNV8 =

Readers:
- DGNV8_1: DGNV8 from $(SourceDataset_DGNV8) in EPSG:2154

Writers:
- SHAPEFILE_1: SHAPEFILE to $(DestDataset_SHAPEFILE)
- OGCGEOPACKAGE_1: OGCGEOPACKAGE to $(DestDataset_OGCGEOPACKAGE) in EPSG:2154

Errors_cls_65 (reader DGNV8_1)
    -> Table1 (writer OGCGEOPACKAGE_1)
Table1 (writer OGCGEOPACKAGE_1)
